submodule openconfig-hercules-platform-port {

  yang-version "1";

  belongs-to openconfig-hercules-platform {
    prefix "herc-platform";
  }

  // import some basic types
  import openconfig-extensions { prefix oc-ext; }
  import openconfig-platform { prefix oc-platform; }
  import openconfig-if-ethernet { prefix oc-eth; }

  // meta
  organization
    "OpenConfig Hercules Working Group";

  contact
    "openconfig-hercules@googlegroups.com";

  description
    "This submodule defines schema extensions to the
    OpenConfig port model for the Hercules switch profile.";

  oc-ext:openconfig-version "0.2.0";

  revision 2017-12-20 {
    description
      "Initial version";
    reference "0.2.0";
  }

  // extension statements

  // feature statements

  // identity statements

  identity SPEED_20GB {
    base oc-eth:ETHERNET_SPEED;
    description "20 GBps Ethernet";
  }

  // typedef statements

  // grouping statements

  grouping hercules-port-config {
    description
      "Configuration data for vendor-agnostic switch port
      components";

    leaf port-id {
      type uint32;
      description
        "References the hardware port in the device inventory";
    }
  }

  grouping hercules-port-state {
    description
      "Operational state data for vendor-agnostic switch port
      components";
  }

  // data definition statements

  // augment statements
  augment "/oc-platform:components/oc-platform:component/" +
          "oc-platform:port/oc-platform:config" {
    description
      "Configuration data for vendor-agnostic switch port components";

    uses hercules-port-config;
  }

  // augment statements
  augment "/oc-platform:components/oc-platform:component/" +
          "oc-platform:port/oc-platform:state" {
    description
      "Operational state data for vendor-agnostic switch port components";

    uses hercules-port-config;
    uses hercules-port-state;
  }

  // rpc statements

  // notification statements

}
