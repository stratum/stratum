module openconfig-hercules-interfaces {
  yang-version "1";


  // namespace
  namespace "http://openconfig.net/yang/hercules/interfaces";

  prefix  "herc-if";

  // import some basic types
  import openconfig-interfaces { prefix oc-if; }
  import openconfig-if-ethernet { prefix oc-eth; }
  import openconfig-extensions { prefix oc-ext; }

  // meta
  organization
      "OpenConfig Hercules Working Group";

  contact
      "openconfig-hercules@googlegroups.com";

  description
    "Hercules extensions to OpenConfig interface model.";

  oc-ext:openconfig-version "0.2.0";

  revision 2017-11-15 {
    description "Still a draft. Expect significant changes.";
    reference "0.2.0";
  }


  // grouping statements

  grouping hercules-interface-eth-config {
    description
      "Configuration data for Hercules Ethernet interfaces.";

    leaf forwarding-viable {
      type boolean;
      default true;
      description
        "This value indicates whether the interface may be used
        to route traffic or not.  If set to false, the
        interface is not used for forwarding traffic, but as long as
        it is up, the interface still maintains its layer-2
        adjacencies and runs its configured layer-2 functions
        (e.g., LLDP, etc.).";
    }
  }

  grouping hercules-interface-config {
    description
      "Configuration data for Hercules interfaces";

    leaf health-indicator {
      type enumeration {
        enum GOOD {
          description
            "Sets the indicator to show the interface health, for
            the purposes of protocol operations, is good / normal.";
        }
        enum BAD {
          description
            "Sets the indicator to show that the interface health,
            for the purposes of protocol operations, is
            bad / failed.";
        }
      }
      description
        "This allows a management or control system to set the health
        state of an interface for the purposes of protocol
        operations.  The state can be used to set indicators, such
        as as a port LED, to visually indicate its health.  If the
        interface is part of a channelized physical port, the device
        should consider the health across all associated
        interfaces, and set the port LED accordingly.  The health
        indicator applies to physical interfaces such as Ethernet
        interfaces, not logical interfaces such as routed VLANs or
        loopbacks.";
    }

  }

  grouping hercules-interface-state {
    description
      "Hercules-specific operational state data";

  }

  // data definition statements

  // augment statements
  augment "/oc-if:interfaces/oc-if:interface/oc-if:config" {

    description
      "Adds Hercules-specific configuration to the interface module";

    uses hercules-interface-config;
  }

  augment "/oc-if:interfaces/oc-if:interface/oc-if:state" {

    description
      "Adds Hercules-specific status information to the interface module";

    uses hercules-interface-config;
    uses hercules-interface-state;
  }

  augment "/oc-if:interfaces/oc-if:interface/oc-eth:ethernet/" +
    "oc-eth:config" {

    description
      "Augments Hercules-specific configuration data for Ethernet
      interfaces.";

    uses hercules-interface-eth-config;
  }

  augment "/oc-if:interfaces/oc-if:interface/oc-eth:ethernet/" +
    "oc-eth:state" {

    description
      "Augments Hercules-specific operational state data for Ethernet
      interfaces.";

    uses hercules-interface-eth-config;
  }

  // rpc statements

  // notification statements

}
