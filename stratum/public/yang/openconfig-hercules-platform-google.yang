module google-hercules {
  yang-version "1";

  // namespace
  namespace "http://google.com/yang/hercules/google-hercules";

  prefix goog-herc;

  // import some basic types
  import hercules-platform { prefix herc-platform; }

  // meta
  organization "Google Inc., PiE Team";
  contact "tmadejski@google.com";
  description
    "Google Extensions to Hercules YANG Model for Vendor Agnostic Stack.";

  oc-ext:openconfig-version "0.2.0";

  revision 2017-11-15 {
    description "Still a draft. Expect significant changes.";
    reference "0.2.0";
  }

  // extension statements

  // feature statements

  // identity statements
  identity MLNX-SN2700 {
    base herc-platform:PLATFORM_TYPE;
    description
      "Platform type: Melonox's SN2070";
  }

  identity P4-SOFT-SWITCH {
    base herc-platform:PLATFORM_TYPE;
    description
      "Platform type: P4's Soft Switch";
  }

  // typedef statements

  // grouping statements

  // data definition statements

  // augment statements

  // rpc statements

  // notification statements

}
